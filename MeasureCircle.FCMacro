__Name__ = 'Measure Circle'
__Comment__ = 'Compute the radius of a circle by 3 points or a circular edge'
__Web__ = 'http://www.freecadweb.org/wiki/Macro_MeasureCircle'
__Wiki__ = 'http://www.freecadweb.org/wiki/Macro_MeasureCircle'
__Icon__ = 'MeasureCircle.svg'
__Help__ = 'Make a selection of 3 points or an edge and launch, or launch first'
__Author__ = 'peepsalot, galou_breizh'
__Version__ = '0.9'
__Status__ = 'Beta'
__Requires__ = ''

import FreeCAD as App
import FreeCADGui as Gui
import Part

from PySide import QtCore, QtGui


class MeasureCircle:
    """Report the radius and center of a circle

    This class will report the computed radius and center of a circle given 3
    vertices or a circular edge.
    A line is drawn from the center of the circle to the first vertex, which
    may be used for future measurements.

    Just select the vertices and the result will be shown in the Report View.
    Edges may also be selected and count as two vertices.
    A circular edge can also be selected.
    If two edges are selected the end vertex of the second edge is not
    used in the calculation.
    """
    def __init__(self):
        self.points = []
        self.curve = None
        self.observer_added = False
        self.getElementsFromSelectionEx()
        # We add the observer only if necessary.
        self.observer_added = (self.curve is None)
        if self.observer_added:
            Gui.Selection.addObserver(self)
            App.Console.PrintMessage(
                'Select {} vertices on a circle or an arc of circle\n'.format(
                    3 - len(self.points)))

    def addSelection(self, doc, obj, sub, pos):
        o = App.getDocument(doc).getObject(obj)
        # Get the shape of selected object, if any.
        try:
            shape = o.Shape
        except AttributeError:
            App.Console.PrintMessage('Object is not a shape\n')
            return
        # Get the selected subshape.
        try:
            subshape = getattr(shape, sub)
        except:
            return
        if subshape.ShapeType == 'Vertex':
            self.addPoint(subshape)
        elif subshape.ShapeType == 'Edge':
            self.onEdge(subshape)
        # Exit if we have enough points.
        if len(self.points) >= 3:
            self.onThreePoints()

    def getElementsFromSelectionEx(self):
        for sel_object in Gui.Selection.getSelectionEx():
            for subobject in sel_object.SubObjects:
                if type(subobject) == Part.Vertex:
                    self.addPoint(subobject)
                elif type(subobject) == Part.Edge:
                    self.onEdge(subobject)
                # Exit if we have enough points.
                if len(self.points) >= 3:
                    self.onThreePoints()
                    return

    def addPoint(self, v):
        for p in self.points:
            if p.Point == v.Point:
                # Don't allow duplicate points.
                return
        self.points.append(v)

    def onEdge(self, edge):
        curve_type = type(edge.Curve)
        if curve_type == Part.Circle:
            self.onCircle(edge.Curve)
        elif curve_type == Part.Line:
            self.addPoint(edge.Vertexes[0])
            self.addPoint(edge.Vertexes[1])

    def finish(self):
        if self.curve:
            c = self.curve
            # line = Part.makeLine(c.Center, c.Center + c.XAxis * c.Radius)
            # obj = App.ActiveDocument.addObject('Part::Feature', 'Radius')
            # obj.Shape = line
            App.Console.PrintMessage('Diameter: {} mm\n'.format(2 * c.Radius))
            App.Console.PrintMessage('Radius: {} mm\n'.format(c.Radius))
            App.Console.PrintMessage(
                'Center: (X, Y, Z) = ({}, {}, {})\n'.format(
                    *list(c.Center)))
        
        if self.observer_added:
            Gui.Selection.removeObserver(self)
        #msg='Diameter: {} mm\n'.format(2 * c.Radius)
        def measure(msg):
            diag = QtGui.QMessageBox(QtGui.QMessageBox.Information, 'Curve Diameter Measurement', msg)
            diag.setWindowModality(QtCore.Qt.ApplicationModal)
            diag.exec_()
        msg='Diameter = {} mm\n'.format(2 * c.Radius) +  'Radius = {} mm\n'.format(c.Radius) + 'Center: (X, Y, Z) = ({}, {}, {})\n'.format(
                    *list(c.Center))
        measure(msg)
        #raise(Exception(msg)) 
        

    def onCircle(self, curve):
        self.curve = curve
        self.finish()

    def onThreePoints(self):
        v1 = self.points[0].Point
        v2 = self.points[1].Point
        v3 = self.points[2].Point
        self.curve = Part.Arc(v1, v2, v3).toShape().Curve
        self.finish()

   

if __name__ == "__main__":
    MeasureCircle()
